(defun c:rings ( / p1 p2 rad qty)
  (setq qty (getint "\nHow many rings? <5>: "))
  (if (= qty nil) (setq qty 5))
	(while (setq p1 (getpoint "\nCenter point: " ))
  		(progn
    			(setq rad 1.0)
    			(command "circle" p1 rad "")
    			(while (< rad qty)
      				(setq rad (1+ rad))
      				(command "circle" p1 rad "")
    			)
   		)
 	)
  	(princ)
)
